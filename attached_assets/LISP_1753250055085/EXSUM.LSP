(DEFUN C:STRUCTURE()
(SETQ TYPEOFSTRUCTURE(GETSTRING "GIVE TYPE OF STRUCTURE Column/Beam/Lintel/Sunshade TYPE C OR B OR L OR S ;"))
(IF (= TYPEOFSTRUCTURE "L") (COMMAND "LINTEL") *CANCLE*)
(IF (= TYPEOFSTRUCTURE "S") (COMMAND "SUNSHADE") *CANCLE*)
(IF (= TYPEOFSTRUCTURE "C") (SETQ SHAPEOFCOLUMN(GETSTRING "GIVE SHAPE OF COLUMN Rectangular OR Circular TYPE R OR C ;")) *CANCLE*)
(IF (= TYPEOFSTRUCTURE "C") (IF (= SHAPEOFCOLUMN "R") (COMMAND "FOOTSQR") *CANCLE*) *CANCLE*)
(IF (= TYPEOFSTRUCTURE "C") (IF (= SHAPEOFCOLUMN "C") (COMMAND "COLUCRCL") *CANCLE*) *CANCLE*)
(IF (= TYPEOFSTRUCTURE "B") (SETQ SHAPEOFBEAM(GETSTRING "GIVE SHAPE OF BEAM Rectangular OR Tee OR L OR Invertedtee TYPE R OR T OR L OR IT ;")) *CANCLE*)
(IF (= TYPEOFSTRUCTURE "B") (IF (= SHAPEOFBEAM "R") (COMMAND "BEAMRECT") *CANCLE*) *CANCLE*)
(IF (= TYPEOFSTRUCTURE "B") (IF (= SHAPEOFBEAM "T") (COMMAND "BEAMTEE") *CANCLE*) *CANCLE*)
(IF (= TYPEOFSTRUCTURE "B") (IF (= SHAPEOFBEAM "L") (COMMAND "BEAML") *CANCLE*) *CANCLE*)
(IF (= TYPEOFSTRUCTURE "B") (IF (= SHAPEOFBEAM "IT") (COMMAND "BEAMINTEE") *CANCLE*) *CANCLE*)





(DEFUN C:LINTEL()
(SETQ B(GETINT "GIVE VALUE OF WEB WIDTH IN MM;"))
(SETQ D(GETINT "GIVE VALUE OF TOTAL DEPTH IN MM;"))
(SETQ DIAB(GETINT "GIVE DIA OF BOTTOM BARS IN MM;"))
(SETQ NBB(GETINT "GIVE NUMBER OF BOTTOM BARS ;"))
(SETQ DIAT(GETINT "GIVE DIA OF TOP BARS IN MM;"))
(SETQ NBT(GETINT "GIVE NUMBER OF TOP BARS ;"))
(SETQ DIAS(GETINT "GIVE DIA OF SHEAR STIRRUPS BARS IN MM;"))
(SETQ SPC(GETINT "GIVE SPACING OF SHEAR STIRRUPS IN MM;"))
(SETQ SCALE(GETINT "GIVE DRAWING SCALE 1: ?  ;"))
(SETQ LINTELNUM(GETSTRING "GIVE LINTEL NUMBER ;"))
(SETQ DIMTEXT (* 3 SCALE))
(SETQ PT1(GETPOINT "PICK FIRST CORNER OF THE BEAM ;"))
(SETQ PT2(LIST(+ (NTH 0 PT1) B)(NTH 1 PT1)))
(SETQ PT3(LIST(NTH 0 PT2)(+ (NTH 1 PT2) D)))
(SETQ PT4(LIST(NTH 0 PT1)(NTH 1 PT3)))
(SETQ DDASB (+ 25 (/ DIAB 2)))
(SETQ DDAST (+ 25 (/ DIAT 2)))
(SETQ PT5(LIST(+ (NTH 0 PT1) DDASB)(+ (NTH 1 PT1) DDASB)))
(SETQ PT6(LIST(+ (NTH 0 PT1) DDAST)(- (NTH 1 PT4) DDAST)))
(SETQ PTC1(LIST(+ (NTH 0 PT5) (* 0.25 DIAB))(NTH 1 PT5)))
(SETQ PTC2(LIST(+ (NTH 0 PT6) (* 0.25 DIAT))(NTH 1 PT6)))
(SETQ PT6(LIST(+ (NTH 0 PT1) DDAST)(- (NTH 1 PT4) DDAST)))
(SETQ SPACINGB (/ (- B (* 2 DDASB)) (- NBB 1)))
(SETQ SPACINGT (/ (- B (* 2 DDAST)) (- NBT 1)))
(COMMAND "DONUT" 0 DIAB PT5 NIL)
(COMMAND "DONUT" 0 DIAT PT6 NIL)
(SETQ PTD1(LIST(NTH 0 PT1)(- (NTH 1 PT1) (* 1.2 DIMTEXT))))
(SETQ PTD2(LIST(- (NTH 0 PT1) (* 1.2 DIMTEXT))(NTH 1 PT1)))
(SETQ PTD3(LIST(NTH 0 PT5)(NTH 1 PT5)))
(SETQ PTD4(LIST(NTH 0 PTD3)(+ (NTH 1 PTD3) (* 0.2 D))))
(SETQ PTD5(LIST(+ (NTH 0 PTD4) B)(NTH 1 PTD4)))
(SETQ PTD6(LIST(NTH 0 PT6)(NTH 1 PT6)))
(SETQ PTD7(LIST(NTH 0 PTD6)(- (NTH 1 PTD6) (* 0.2 D))))
(COMMAND "ARRAY" "SI" PTC1 "R" "1" NBB SPACINGB)
(COMMAND "LINE" PTD3 PTD4 *CANCEL*)
(SETQ PTD8(LIST(+ (NTH 0 PTD7) B)(NTH 1 PTD7)))
(COMMAND "ARRAY" "SI" PTC2 "R" "1" NBT SPACINGT)
(COMMAND "LINE" PTD6 PTD7 *CANCEL*)
(COMMAND "ARRAY" "SI" PTD7 "R" "1" NBT SPACINGT)
(COMMAND "DDIM" "RAJ25SCALE")
(COMMAND "ARRAY" "SI" PTD3 "R" "1" NBB SPACINGB)
(COMMAND "DDIM" "RAJ25SCALE")
(COMMAND "PLINE" PT1 PT2 PT3 PT4 "C")
(COMMAND "OFFSET" "25" PT1 PT5 *CANCEL*)
(COMMAND "DIM" "HORIZONTAL" PT1 PT2 "T" B PTD1 *CANCLE*)
(COMMAND "DIM" "VERTICAL" PT1 PT4 "T" D PTD2 *CANCEL*)
(SETQ PTD9(LIST(- (NTH 0 PT2) 25)(+ (NTH 1 PT2) (* 0.50 D))))
(SETQ PTD10(LIST(+ (NTH 0 PTD9) (+ 25 DDASB))(NTH 1 PTD9)))
(COMMAND "LINE" PTD4 PTD5 *CANCEL*)
(COMMAND "LINE" PTD7 PTD8 *CANCEL*)
(COMMAND "LINE" PTD9 PTD10 *CANCEL*)
(SETQ NOTE (STRCAT (ITOA NBB) "NOS." (ITOA DIAB) "MM DIA.TOR BARS"))
(COMMAND "TEXT" PTD5 (* 0.1 D) "0" NOTE)
(SETQ NOTE (STRCAT (ITOA NBT) "NOS." (ITOA DIAT) "MM DIA.TOR BARS"))
(COMMAND "TEXT" PTD8 (* 0.1 D) "0" NOTE)
(SETQ NOTE (STRCAT (ITOA DIAS) "MM DIA.TWO LEGGED STIRRUPS @" (ITOA SPC) "MM C/C."))
(COMMAND "TEXT" PTD10 (* 0.1 D) "0" NOTE)
(SETQ PTD11(LIST(NTH 0 PT1)(- (NTH 1 PT1) (* 4 DIMTEXT))))
(SETQ NOTE (STRCAT "%%ULINTEL NO.L-%%U" LINTELNUM))
(COMMAND "TEXT" PTD11 (* 0.125 D) "0" NOTE)
(COMMAND "ZOOM" "C" PTD10 (* 3 D)) 
)



(DEFUN C:SUNSHADE()
(SETQ B(GETINT "GIVE VALUE OF WEB WIDTH IN MM;"))
(SETQ D(GETINT "GIVE VALUE OF TOTAL DEPTH IN MM;"))
(SETQ PROJ(GETINT "GIVE VALUE OF PROJECTION OF THE SUNSHADE IN MM;"))
(SETQ THICKSUP(GETINT "GIVE VALUE OF SUNSHADE THICKNESS NEAR SUPPORT IN MM;"))
(SETQ THICKEDG(GETINT "GIVE VALUE OF SUNSHADE THICKNESS AT THE OUTER EDGE IN MM;"))
(SETQ DIAB(GETINT "GIVE DIA OF BOTTOM BARS IN MM;"))
(SETQ NBB(GETINT "GIVE NUMBER OF BOTTOM BARS ;"))
(SETQ DIAT(GETINT "GIVE DIA OF TOP BARS IN MM;"))
(SETQ NBT(GETINT "GIVE NUMBER OF TOP BARS ;"))
(SETQ DIAS(GETINT "GIVE DIA OF SHEAR STIRRUPS BARS IN MM;"))
(SETQ SPC(GETINT "GIVE SPACING OF SHEAR STIRRUPS IN MM;"))
(SETQ DIASMAIN(GETINT "GIVE DIA OF SUNSHADE MAIN BARS IN MM;"))
(SETQ DIASDIS(GETINT "GIVE DIA OF SUNSHADE DISTRIBUTION BARS IN MM;"))
(SETQ SPCDIS(GETINT "GIVE SPACING OF SUNSHADE DISTRIBUTION BARS IN MM;"))
(SETQ SCALE(GETINT "GIVE DRAWING SCALE 1: ?  ;"))
(SETQ SUNSHADENUM(GETSTRING "GIVE SUNSHADE NUMBER ;"))
(SETQ DIMTEXT(* 3 SCALE))
(SETQ PT1(GETPOINT "PICK FIRST CORNER OF THE SUNSHADE ;"))
(SETQ PT2(LIST(+ (NTH 0 PT1) B)(NTH 1 PT1)))
(SETQ PT3(LIST(NTH 0 PT2)(+ (NTH 1 PT2) D)))
(SETQ PT4(LIST(NTH 0 PT1)(NTH 1 PT3)))
(SETQ PT201(LIST(+ (NTH 0 PT1) 25)(+ (NTH 1 PT1) 25)))
(SETQ PT202(LIST(- (NTH 0 PT2) 25)(NTH 1 PT201)))
(SETQ PT203(LIST(NTH 0 PT202)(- (NTH 1 PT3) 25)))
(SETQ PT204(LIST(NTH 0 PT201)(NTH 1 PT203)))
(SETQ DDASB(+ 25 (/ DIAB 2)))
(SETQ DDAST(+ 25 (/ DIAT 2)))
(SETQ PT5(LIST(+ (NTH 0 PT1) DDASB)(+ (NTH 1 PT1) DDASB)))
(SETQ PT6(LIST(+ (NTH 0 PT1) DDAST)(- (NTH 1 PT4) DDAST)))
(SETQ PTC1(LIST(+ (NTH 0 PT5) (* 0.25 DIAB))(NTH 1 PT5)))
(SETQ PTC2(LIST(+ (NTH 0 PT6) (* 0.25 DIAT))(NTH 1 PT6)))
(SETQ PT6(LIST(+ (NTH 0 PT1) DDAST)(- (NTH 1 PT4) DDAST)))
(SETQ PT105(LIST(NTH 0 PT2)(+ (NTH 1 PT2) THICKSUP)))
(SETQ PT106(LIST(NTH 0 PT2)(NTH 1 PT2)))
(SETQ PT107(LIST(+ (NTH 0 PT105) PROJ)(+ (NTH 1 PT2) THICKEDG)))
(SETQ PT108(LIST(NTH 0 PT107)(NTH 1 PT2)))
(SETQ PT201(LIST(+ (NTH 0 PT1) 25)(+ (NTH 1 PT1) 25)))
(SETQ PT202(LIST(- (NTH 0 PT2) 25)(NTH 1 PT201)))
(SETQ PT203(LIST(NTH 0 PT202)(- (NTH 1 PT3) 25)))
(SETQ PT204(LIST(NTH 0 PT201)(NTH 1 PT203)))
(SETQ PT205(LIST(NTH 0 PT202)(+ (NTH 1 PT202) PROJ)))
(SETQ PT206(LIST(NTH 0 PT205)(+ (NTH 1 PT205) (- THICKEDG 50))))
(SETQ SPACINGB(/ (- B (* 2 DDASB)) (- NBB 1)))
(SETQ SPACINGT(/ (- B (* 2 DDAST)) (- NBT 1)))
(COMMAND "DONUT" 0 DIAB PT5 NIL)
(COMMAND "DONUT" 0 DIAT PT6 NIL)
(SETQ PTD1(LIST(NTH 0 PT1)(- (NTH 1 PT1) (* 1.2 DIMTEXT))))
(SETQ PTD111(LIST(NTH 0 PT2)(- (NTH 1 PT1) (* 1.2 DIMTEXT))))
(SETQ PTD2(LIST(- (NTH 0 PT1) (* 1.5 DIMTEXT))(NTH 1 PT1)))
(SETQ PTD3(LIST(NTH 0 PT5)(NTH 1 PT5)))
(SETQ PTD4(LIST(NTH 0 PTD3)(+ (NTH 1 PTD3) (* 0.25 D))))
(SETQ PTD5(LIST(+ (NTH 0 PTD4) B)(NTH 1 PTD4)))
(SETQ PTD6(LIST(NTH 0 PT6)(NTH 1 PT6)))
(SETQ PTD7(LIST(NTH 0 PTD6)(+ (NTH 1 PTD5) (* 0.35 D))))
(COMMAND "ARRAY" "SINGLE" PTC1 "RECTANGULAR" "1" NBB SPACINGB)
(COMMAND "LINE" PTD3 PTD4 *CANCEL*)
(COMMAND "ARRAY" "SINGLE" PTD4 "RECTANGULAR" "1" NBB SPACINGB)
(SETQ PTD8(LIST(+ (NTH 0 PTD7) B)(NTH 1 PTD7)))
(COMMAND "ARRAY" "SINGLE" PTC2 "RECTANGULAR" "1" NBT SPACINGT)
(COMMAND "LINE" PTD6 PTD7 *CANCEL*)
(COMMAND "ARRAY" "SINGLE" PTD7 "RECTANGULAR" "1" NBT SPACINGT)
(COMMAND "PLINE" PT201 PT202 PT203 PT204 "C")
(COMMAND "PLINE" PT1 PT108 PT107 PT105 PT3  PT4 "C" *CANCLE*)
(COMMAND "DIM" "HORIZONTAL" PT1 PT2 "T" B PTD1 *CANCLE*)
(COMMAND "DIM" "HORIZONTAL" PT2 PT108 "T" PROJ PTD111 *CANCLE*)
(COMMAND "DIM" "VERTICAL" PT1 PT4 "T" D PTD2 *CANCEL*)
(SETQ PTD101(LIST(+ (NTH 0 PT108) THICKSUP)(NTH 1 PT108)))
(SETQ PTD102(LIST(+ (NTH 0 PTD101) (* 1 DIMTEXT))(NTH 1 PTD101)))
(SETQ PT105DAS(LIST(+ (NTH 0 PT105) (+ PROJ THICKSUP))(NTH 1 PT105)))
(SETQ PT106DAS(LIST(NTH 0 PT105DAS)(NTH 1 PT106)))
(COMMAND "DIM" "VERTICAL" PT105DAS PT106DAS "T" THICKSUP PTD101 *CANCEL*)
(COMMAND "DIM" "VERTICAL" PT107 PT108 "T" THICKEDG PTD102 *CANCEL*)
(SETQ PTD9(LIST(- (NTH 0 PT2) 25)(+ (NTH 1 PTD5) (* 0.2 D))))
(SETQ PTD10(LIST(NTH 0 PTD5)(NTH 1 PTD9)))
(COMMAND "LINE" PTD4 PTD5 *CANCEL*)
(COMMAND "LINE" PTD7 PTD8 *CANCEL*)
(COMMAND "LINE" PTD9 PTD10 *CANCEL*)
(SETQ NOTE (STRCAT (ITOA NBB) "NOS." (ITOA DIAB) "MM DIA.TOR BARS"))
(COMMAND "TEXT" PTD5 (* 0.1 D) "0" NOTE)
(SETQ NOTE (STRCAT (ITOA NBT) "NOS." (ITOA DIAT) "MM DIA.TOR BARS"))
(COMMAND "TEXT" PTD8 (* 0.1 D) "0" NOTE)
(SETQ NOTE (STRCAT (ITOA DIAS) "MM DIA.TWO LEGGED STIRRUPS @" (ITOA SPC) "MM C/C."))
(COMMAND "TEXT" PTD10 (* 0.1 D) "0" NOTE)
(SETQ PTD11(LIST(NTH 0 PT1)(- (NTH 1 PT1) (* 4 DIMTEXT))))
(SETQ NOTE (STRCAT "%%USUNSHADE NO.SS-%%U" SUNSHADENUM))
(COMMAND "TEXT" PTD11 (* 0.125 D) "0" NOTE)
(COMMAND "ZOOM" "C" PTD10 (* 3.5 D))
(SETQ R1(+ B PROJ))
(SETQ R2(FLOAT(- R1 50)))
(SETQ R3(FLOAT(- THICKSUP THICKEDG)))
(SETQ R4(FLOAT(/ R3 PROJ)))
(SETQ R(* R2 R4))
(SETQ PT503(LIST(- (NTH 0 PT108) 25)(+ (NTH 1 PT108) 25)))
(SETQ PT502(LIST(NTH 0 PT503)(- (NTH 1 PT107) 25)))
(SETQ PT501(LIST(NTH 0 PT201)(+ (NTH 1 PT502) R)))
(COMMAND "LINE" PT501 PT502 PT503 *CANCLE*)
(SETQ VCOMPONENT(* R4 SPCDIS))
(SETQ PTDONUT1(LIST(- (NTH 0 PT502) (/ DIASDIS 2))(- (NTH 1 PT502) (/ DIASDIS 2))))
(SETQ PTDONUT2(LIST(- (NTH 0 PTDONUT1) SPCDIS)(+ (NTH 1 PTDONUT1) VCOMPONENT)))
(SETQ PTDONUT3(LIST(- (NTH 0 PTDONUT2) SPCDIS)(+ (NTH 1 PTDONUT2) VCOMPONENT)))
(SETQ PTDONUT4(LIST(- (NTH 0 PTDONUT3) SPCDIS)(+ (NTH 1 PTDONUT3) VCOMPONENT)))
(SETQ PTDONUT5(LIST(- (NTH 0 PTDONUT4) SPCDIS)(+ (NTH 1 PTDONUT4) VCOMPONENT)))
(SETQ PTDONUT6(LIST(- (NTH 0 PTDONUT5) SPCDIS)(+ (NTH 1 PTDONUT5) VCOMPONENT)))
(SETQ PTDONUT7(LIST(- (NTH 0 PTDONUT6) SPCDIS)(+ (NTH 1 PTDONUT6) VCOMPONENT)))
(SETQ PTDONUT8(LIST(- (NTH 0 PTDONUT7) SPCDIS)(+ (NTH 1 PTDONUT7) VCOMPONENT)))
(SETQ PTDONUT9(LIST(- (NTH 0 PTDONUT8) SPCDIS)(+ (NTH 1 PTDONUT8) VCOMPONENT)))
(COMMAND "DONUT" 0 DIASDIS PTDONUT1 *CANCLE*)
(COMMAND "DONUT" 0 DIASDIS PTDONUT2 *CANCLE*)
(COMMAND "DONUT" 0 DIASDIS PTDONUT3 *CANCLE*)
(COMMAND "DONUT" 0 DIASDIS PTDONUT4 *CANCLE*)
(SETQ NODIS(+ (/ PROJ SPCDIS) 1))
(IF (> NODIS 4) (COMMAND "DONUT" 0 DIASDIS PTDONUT5 *CANCLE*) *CANCLE*)
(IF (> NODIS 5) (COMMAND "DONUT" 0 DIASDIS PTDONUT6 *CANCLE*) *CANCLE*)
(IF (> NODIS 6) (COMMAND "DONUT" 0 DIASDIS PTDONUT7 *CANCLE*) *CANCLE*)
(IF (> NODIS 7) (COMMAND "DONUT" 0 DIASDIS PTDONUT8 *CANCLE*) *CANCLE*)
(IF (> NODIS 8) (COMMAND "DONUT" 0 DIASDIS PTDONUT9 *CANCLE*) *CANCLE*)
)



(DEFUN C:FOOTSQR()
(SETQ B(GETINT "GIVE VALUE OF WIDTH OF COLUMN IN MM;"))
(SETQ D(GETINT "GIVE VALUE OF TOTAL DEPTH OF COLUMN IN MM;"))
(SETQ DIAL(GETINT "GIVE DIA OF LONGITUDINAL REINFORCEMENT BARS OF COLUMN IN MM;"))
(SETQ NBTOTAL(GETINT "GIVE TOTAL NUMBER OF BARS IN THE COLUMN;"))
(SETQ NBF(GETINT "GIVE NUMBER OF BARS ON EACH FLANGE OF COLUMN;"))
(SETQ NBS1(/ (- (FLOAT NBTOTAL) (* 2 (FLOAT NBF))) 2))
(SETQ NBS2(+ 0.5 NBS1))
(SETQ NBS(FIX NBS2))
(SETQ DIAT(GETINT "GIVE DIA OF LATERAL TIES OF COLUMN IN MM;"))
(SETQ SPC(GETINT "GIVE SPACING OF LATERAL TIES OF COLUMN IN MM;"))
(SETQ BFOOTING(GETINT "GIVE WIDTH OF COLUMN FOOTING IN MM;"))
(SETQ DEPTHEDGE(GETINT "GIVE DEPTH OF FOOTING AT EDGE IN MM;"))
(SETQ DEPTHCENTRE(GETINT "GIVE DEPTH OF FOOTING NEAR CENTRE IN MM;"))
(SETQ PCCPROJECTION(GETINT "GIVE PROJECTION OF PCC IN MM;"))
(SETQ PCCTHICKNESS(GETINT "GIVE THICKNESS OF PCC IN MM;"))
(SETQ PEDASTALPROJECTION(GETINT "GIVE PROJECTION OF PEDASTAL AT BASE OF THE COLUMN IN MM;"))
(SETQ DIAFOOTX(GETINT "GIVE DIA OF FOOTING REINFORCEMENT BARS IN X-DIRECTION IN MM;"))
(SETQ SPCX(GETINT "GIVE SPACING OF FOOTING REINFORCEMENT BARS IN X-DIRECTION IN MM;"))
(SETQ DIAFOOTY(GETINT "GIVE DIA OF FOOTING REINFORCEMENT BARS IN Y-DIRECTION IN MM;"))
(SETQ SPCY(GETINT "GIVE SPACING OF FOOTING REINFORCEMENT BARS IN Y-DIRECTION IN MM;"))
(SETQ SCALE(GETINT "GIVE DRAWING SCALE 1: ?  ;"))
(SETQ COLUMNUM(GETSTRING "GIVE COLUMN NUMBER C- ;"))
(SETQ DIMTEXT (* 3 SCALE))
(SETQ PT1(GETPOINT "PICK FIRST CORNER OF THE COLUMN ;"))
(SETQ PT2(LIST(+ (NTH 0 PT1) B)(NTH 1 PT1)))
(SETQ PT3(LIST(NTH 0 PT2)(+ (NTH 1 PT2) D)))
(SETQ PT4(LIST(NTH 0 PT1)(NTH 1 PT3)))
(SETQ DDASL (+ 25 (/ DIAL 2)))
(SETQ PT5(LIST(+ (NTH 0 PT1) DDASL)(+ (NTH 1 PT1) DDASL)))
(SETQ PT6(LIST(NTH 0 PT5)(- (NTH 1 PT4) DDASL)))
(SETQ PTC1(LIST(+ (NTH 0 PT5) (* 0.25 DIAL))(NTH 1 PT5)))
(SETQ SPACINGH (/ (- B (* 2 DDASL)) (- NBF 1)))
(SETQ SPACINGV (/ (- D (* 2 DDASL)) (- (+ NBS 2) 1)))
(COMMAND "DONUT" 0 DIAL PT5 NIL)
(COMMAND "ARRAY" "SI" PTC1 "RECTANGULAR" "2" NBF (- D (* 2 DDASL)) SPACINGH *CANCLE*)
(SETQ PTD1(LIST(NTH 0 PT1)(- (NTH 1 PT1) (* 1.75 DIMTEXT))))
(SETQ PTD2(LIST(- (NTH 0 PT1) (* 1.75 DIMTEXT))(NTH 1 PT1)))
(SETQ PTD3(LIST(NTH 0 PT5)(NTH 1 PT5)))
(SETQ PTD4(LIST(NTH 0 PTD3)(+ (NTH 1 PTD3) (* 0.2 D))))
(SETQ PTD5(LIST(+ (NTH 0 PTD4) B)(NTH 1 PTD4)))
(SETQ PTD6(LIST(NTH 0 PT6)(NTH 1 PT6)))
(SETQ PTD7(LIST(NTH 0 PTD6)(- (NTH 1 PTD6) (* 0.2 D))))
(SETQ PT7(LIST(NTH 0 PT5)(+ SPACINGV (NTH 1 PT5))))
(IF (= NBS 0) *CANCLE* (COMMAND "DONUT" 0 DIAL PT7 NIL))
(SETQ PTC2(LIST(+ (NTH 0 PT7) (* 0.25 DIAL))(NTH 1 PT7)))
(IF (= NBS 1) (COMMAND "ARRAY" "SI" PTC2 "RECTANGULAR" "1" 2 (- B (* 2 DDASL)) *CANCLE*) *CANCLE*)
(IF (= NBS 2) (COMMAND "ARRAY" "SI" PTC2 "RECTANGULAR" NBS 2 SPACINGV (- B (* 2 DDASL)) *CANCLE*) *CANCLE*)
(IF (= NBS 3) (COMMAND "ARRAY" "SI" PTC2 "RECTANGULAR" NBS 2 SPACINGV (- B (* 2 DDASL)) *CANCLE*) *CANCLE*)
(IF (= NBS 4) (COMMAND "ARRAY" "SI" PTC2 "RECTANGULAR" NBS 2 SPACINGV (- B (* 2 DDASL)) *CANCLE*) *CANCLE*)
(IF (= NBS 5) (COMMAND "ARRAY" "SI" PTC2 "RECTANGULAR" NBS 2 SPACINGV (- B (* 2 DDASL)) *CANCLE*) *CANCLE*)
(IF (= NBS 6) (COMMAND "ARRAY" "SI" PTC2 "RECTANGULAR" NBS 2 SPACINGV (- B (* 2 DDASL)) *CANCLE*) *CANCLE*)
(IF (= NBS 7) (COMMAND "ARRAY" "SI" PTC2 "RECTANGULAR" NBS 2 SPACINGV (- B (* 2 DDASL)) *CANCLE*) *CANCLE*)
(IF (= NBS 8) (COMMAND "ARRAY" "SI" PTC2 "RECTANGULAR" NBS 2 SPACINGV (- B (* 2 DDASL)) *CANCLE*) *CANCLE*)
(IF (= NBS 9) (COMMAND "ARRAY" "SI" PTC2 "RECTANGULAR" NBS 2 SPACINGV (- B (* 2 DDASL)) *CANCLE*) *CANCLE*)
(COMMAND "LINE" PTD3 PTD4 *CANCEL*)
(SETQ PTD8(LIST(+ (NTH 0 PTD7) B)(NTH 1 PTD7)))
(COMMAND "ARRAY" PTD4 "SI" "RECTANGULAR" "1" NBF SPACINGH *CANCLE*)
(COMMAND "LINE" PTD6 PTD7 *CANCEL*)
(COMMAND "ARRAY" PTD7 "SI" "RECTANGULAR" "1" NBF SPACINGH *CANCLE*)
(COMMAND "PLINE" PT1 PT2 PT3 PT4 "C" *CANCLE*)
(COMMAND "OFFSET" "25" PT1 PT5 *CANCEL*)
(COMMAND "DIM" "HORIZONTAL" PT1 PT2 "T" B PTD1 *CANCLE*)
(COMMAND "DIM" "VERTICAL" PT1 PT4 "T" D PTD2 *CANCEL*)
(SETQ PTD9(LIST(- (NTH 0 PT2) 25)(+ (NTH 1 PT2) (* 0.55 D))))
(SETQ PTD10(LIST(+ (NTH 0 PTD9) (+ 25 DDASL))(NTH 1 PTD9)))
(COMMAND "LINE" PTD4 PTD5 *CANCEL*)
(COMMAND "LINE" PTD7 PTD8 *CANCEL*)
(COMMAND "LINE" PTD9 PTD10 *CANCEL*)
(SETQ NOTE (STRCAT (ITOA NBF) "NOS." (ITOA DIAL) "MM DIA.TOR BARS"))
(COMMAND "TEXT" PTD5 (* 0.1 D) "0" NOTE *CANCLE*)
(SETQ NOTE (STRCAT (ITOA NBF) "NOS." (ITOA DIAL) "MM DIA.TOR BARS"))
(COMMAND "TEXT" PTD8 (* 0.1 D) "0" NOTE *CANCLE*)
(SETQ NOTE (STRCAT (ITOA DIAT) "MM DIA.LATERAL TIES @" (ITOA SPC) "MM C/C."))
(COMMAND "TEXT" PTD10 (* 0.1 D) "0" NOTE *CANCLE*)
(SETQ PTD11(LIST(NTH 0 PT1)(- (NTH 1 PT1) (* 4 DIMTEXT))))
(SETQ NOTE (STRCAT "%%UCOLUMN C-%%U" COLUMNUM))
(COMMAND "TEXT" PTD11 (* 0.125 D) "0" NOTE *CANCLE*)
(SETQ PTD12(LIST(NTH 0 PTD8)(+ (NTH 1 PTD8) (* 0.2 D))))
(SETQ NOTE (STRCAT "TOTAL NO.OF LONGITUDINAL BARS-" (ITOA (* 2 (+ NBF NBS)))))
(COMMAND "TEXT" PTD12 (* 0.1 D) "0" NOTE *CANCLE*)

(SETQ PTPLAN1(LIST(- (NTH 0 PT1) (/ (- bfooting b) 2))(- (NTH 1 PT1) (* BFOOTING 1.5))))
(SETQ PTPLAN2(LIST(+ (NTH 0 PTPLAN1) BFOOTING)(NTH 1 PTPLAN1)))
(SETQ PTPLAN3(LIST(NTH 0 PTPLAN2)(+ (NTH 1 PTPLAN2) BFOOTING)))
(SETQ PTPLAN4(LIST(NTH 0 PTPLAN1)(NTH 1 PTPLAN3)))
(SETQ NOX(+ (/ (- BFOOTING 80) SPCX) 1))
(SETQ NOY(+ (/ (- BFOOTING 80) SPCY) 1))
(SETQ SPCX1(/ (- BFOOTING 80) (- NOX 1)))
(SETQ SPCY1(/ (- BFOOTING 80) (- NOY 1)))
(SETQ PREINFX1(LIST(+ (NTH 0 PTPLAN1) 40)(+ (NTH 1 PTPLAN1) 40)))
(SETQ PREINFX2(LIST(- (NTH 0 PTPLAN2) 40)(NTH 1 PREINFX1)))
(SETQ PREINFY1(LIST(NTH 0 PREINFX1)(NTH 1 PREINFX1)))
(SETQ PREINFY2(LIST(NTH 0 PREINFX1)(- (NTH 1 PTPLAN4) 40)))
(COMMAND "LINE" PREINFX1 PREINFX2 *CANCEL*)
(SETQ PREINFY3(LIST(NTH 0 PREINFX1)(- (NTH 1 PREINFY2) (/ SPCX1 2))))
(COMMAND "ARRAY" PREINFX2 "SI" "RECTANGULAR" NOX "1" SPCX1 *CANCLE*)
(COMMAND "LINE" PREINFY1 PREINFY2 *CANCEL*)
(COMMAND "ARRAY" PREINFY3 "SI" "RECTANGULAR" "1" NOY SPCY1 *CANCLE*)
(COMMAND "LINE" PTPLAN1 PTPLAN2 PTPLAN3 PTPLAN4 PTPLAN1 *CANCEL*)


(SETQ PTPLAND1(LIST(NTH 0 PTPLAN1)(- (NTH 1 PTPLAN1) (* 1.75 DIMTEXT))))
(COMMAND "DIM" "HORIZONTAL" PTPLAN1 PTPLAN2 "T" BFOOTING PTPLAND1 *CANCLE*)
(SETQ PTPLAND2(LIST(- (NTH 0 PTPLAN1) (* 2.5 DIMTEXT))(NTH 1 PTPLAN1)))
(COMMAND "DIM" "VERTICAL" PTPLAN1 PTPLAN4 "T" BFOOTING PTPLAND2 *CANCEL*)
(SETQ PTPLAND3(LIST(- (NTH 0 PREINFX2) (* 3.5 SPCY1))(+ (NTH 1 PREINFX2) (* 2 SPCX1))))
(SETQ PTPLAND4(LIST(NTH 0 PTPLAND3)(+ (NTH 1 PTPLAND3) (* 1.75 DIMTEXT))))
(SETQ PTPLAND5(LIST(+ (NTH 0 PTPLAN2) (* 1.75 DIMTEXT))(NTH 1 PTPLAND4)))
(COMMAND "DIM" "LEADER" PTPLAND3 PTPLAND4 *CANCLE*)
(COMMAND "LINE" PTPLAND4 PTPLAND5 *CANCEL*)
(SETQ NOTE (STRCAT (ITOA DIAFOOTX) "MM DIA.BARS @" (ITOA SPCX) "MM C/C."))
(COMMAND "TEXT" PTPLAND5 (* 0.1 D) "0" NOTE *CANCLE*)
(SETQ PTPLAND6(LIST(+ (NTH 0 PREINFY2) (* (- NOY 3) SPCY1))(- (NTH 1 PREINFY2) (* 1.75 DIMTEXT))))
(SETQ PTPLAND7(LIST(NTH 0 PTPLAND5)(NTH 1 PTPLAND6)))
(COMMAND "DIM" "LEADER" PTPLAND6 PTPLAND7 *CANCLE*)
(COMMAND "LINE" PTPLAND6 PTPLAND7 *CANCEL*)
(SETQ NOTE (STRCAT (ITOA DIAFOOTY) "MM DIA.BARS @" (ITOA SPCY) "MM C/C."))
(COMMAND "TEXT" PTPLAND7 (* 0.1 D) "0" NOTE *CANCLE*)
(SETQ PTPLAND8(LIST(NTH 0 PTPLAN1)(- (NTH 1 PTPLAN1) (* 4 DIMTEXT))))
(SETQ NOTE (STRCAT "%%UPLAN OF FOOTING F-%%U" COLUMNUM))
(COMMAND "TEXT" PTPLAND8 (* 0.125 D) "0" NOTE *CANCLE*)
















(SETQ PTSECTION1(LIST(NTH 0 PTPLAN1)(- (NTH 1 PTPLAN1) (* BFOOTING 1.5))))
(SETQ PTSECTION2(LIST(+ (NTH 0 PTSECTION1) BFOOTING)(NTH 1 PTSECTION1)))
(SETQ PTSECTION3(LIST(NTH 0 PTSECTION2)(+ (NTH 1 PTSECTION2) DEPTHEDGE)))
(SETQ PTSECTION10(LIST(NTH 0 PTSECTION1)(NTH 1 PTSECTION3)))
(SETQ PTSECTION4(LIST(- (NTH 0 PTPLAN3) (- (/ (- bfooting b) 2) PEDASTALPROJECTION))(+ (NTH 1 PTSECTION1) DEPTHCENTRE)))
(SETQ PTSECTION5(LIST(- (NTH 0 PTSECTION4) PEDASTALPROJECTION)(NTH 1 PTSECTION4)))
(SETQ PTSECTION8(LIST(- (NTH 0 PTSECTION5) B)(NTH 1 PTSECTION4)))
(SETQ PTSECTION9(LIST(- (NTH 0 PTSECTION8) PEDASTALPROJECTION)(NTH 1 PTSECTION4)))
(SETQ PTSECTION6(LIST(NTH 0 PTSECTION5)(+ (NTH 1 PTSECTION5) 750)))
(SETQ PTSECTION7(LIST(NTH 0 PTSECTION8)(NTH 1 PTSECTION6)))
(SETQ PTSECTION11(LIST(- (NTH 0 PTSECTION1) PCCPROJECTION)(NTH 1 PTSECTION1)))
(COMMAND "LINE" PTSECTION1 PTSECTION10 PTSECTION9 PTSECTION8 PTSECTION7 *CANCEL*)
(COMMAND "LINE" PTSECTION2 PTSECTION3 PTSECTION4 PTSECTION5 PTSECTION6 *CANCEL*)
(SETQ PTSECTION14(LIST(+ (NTH 0 PTSECTION2) PCCPROJECTION)(NTH 1 PTSECTION1)))
(SETQ PTSECTION13(LIST(NTH 0 PTSECTION14)(- (NTH 1 PTSECTION2) PCCTHICKNESS)))
(SETQ PTSECTION12(LIST(NTH 0 PTSECTION11)(NTH 1 PTSECTION13)))
(SETQ PTSECTION16(LIST(NTH 0 PTSECTION7)(- (NTH 1 PTSECTION7) 450)))
(SETQ PTSECTION17(LIST(NTH 0 PTSECTION6)(NTH 1 PTSECTION16)))
(SETQ PTSECTION15(LIST(- (NTH 0 PTSECTION16) (/ BFOOTING 2))(NTH 1 PTSECTION16)))
(SETQ PTSECTION18(LIST(+ (NTH 0 PTSECTION17) (/ BFOOTING 2))(NTH 1 PTSECTION16)))
(SETQ PTSECTIONC(LIST(+ (NTH 0 PTSECTION12) (/ PCCTHICKNESS 2))(+ (NTH 1 PTSECTION12) (/ PCCTHICKNESS 2))))
(COMMAND "PLINE" PTSECTION11 PTSECTION12 PTSECTION13 PTSECTION14 "C" *CANCLE*)
(COMMAND "LINE" PTSECTION15 PTSECTION16 *CANCLE*)
(COMMAND "LINE" PTSECTION17 PTSECTION18 *CANCLE*)
(SETQ EXT1(/ B 4))
(SETQ EXT2(/ B 2))
(SETQ PTEH101(LIST(- (NTH 0 PTSECTION7) EXT1)(NTH 1 PTSECTION7)))
(SETQ PTEH102(LIST(NTH 0 PTSECTION7)(NTH 1 PTSECTION7)))
(SETQ PTEH103(LIST(+ (NTH 0 PTSECTION7) EXT1)(NTH 1 PTSECTION7)))
(SETQ PTEH104(LIST(+ (NTH 0 PTEH103) EXT1)(- (NTH 1 PTEH103) EXT1)))
(SETQ PTEH105(LIST(NTH 0 PTEH104)(+ (NTH 1 PTEH104) EXT2)))
(SETQ PTEH106(LIST(+ (NTH 0 PTEH105) EXT1)(NTH 1 PTEH103)))
(SETQ PTEH107(LIST(NTH 0 PTSECTION6)(NTH 1 PTSECTION6)))
(SETQ PTEH108(LIST(+ (NTH 0 PTEH107) EXT1)(NTH 1 PTEH103)))
(COMMAND "LINE" PTEH101 PTEH102 PTEH103 PTEH104 PTEH105 PTEH106 PTEH107 PTEH108 *CANCEL*)
(SETQ PSECREINFX1(LIST(NTH 0 PREINFX1)(+ (NTH 1 PTSECTION1) 40)))
(SETQ PSECREINFX2(LIST(NTH 0 PREINFX2)(NTH 1 PSECREINFX1)))
(SETQ PSECREINFY1(LIST(+ (NTH 0 PSECREINFX1) (/ DIAFOOTY 2))(+ (NTH 1 PSECREINFX1) (/ DIAFOOTY 2))))
(SETQ PSECREINFY2(LIST(NTH 0 PSECREINFY1)(+ (NTH 1 PSECREINFY1) (* 0.25 DIAFOOTY))))
(COMMAND "DONUT" 0 DIAFOOTY PSECREINFY1 NIL)
(COMMAND "ARRAY" "SI" PSECREINFY2 "RECTANGULAR" "1" NOY SPCY1 *CANCLE*)
(SETQ PSECREINFL1(LIST(NTH 0 PT5)(NTH 1 PTSECTION7)))
(SETQ PSECREINFL2(LIST(NTH 0 PT5)(+ (NTH 1 PSECREINFX1) 25)))
(SETQ PSECREINFL4(LIST(- (NTH 0 PT2) DDASL)(NTH 1 PTSECTION7)))
(SETQ PSECREINFL5(LIST(NTH 0 PSECREINFL4)(NTH 1 PSECREINFL2)))
(SETQ PSECREINFL3(LIST(- (NTH 0 PSECREINFL2) (* 0.30 BFOOTING))(NTH 1 PSECREINFL2)))
(SETQ PSECREINFL6(LIST(+ (NTH 0 PSECREINFL5) (* 0.30 BFOOTING))(NTH 1 PSECREINFL2)))
(SETQ PSECREINFTIES1(LIST(NTH 0 PSECREINFL2)(+ (NTH 1 PSECREINFL2) (/ SPC 2))))
(SETQ PSECREINFTIES2(LIST(NTH 0 PSECREINFL5)(NTH 1 PSECREINFTIES1)))
(COMMAND "LINE" PSECREINFTIES1 PSECREINFTIES2 *CANCEL*)
(SETQ PSECREINFTIESC(LIST(+ (NTH 0 PSECREINFTIES1) DDASL)(NTH 1 PSECREINFTIES1)))
(SETQ NTIES(FIX (+ (/ (- (NTH 1 PSECREINFL1) (NTH 1 PSECREINFTIES1)) SPC) 1)))
(SETQ SPC1(/ (- (NTH 1 PSECREINFL1) (NTH 1 PSECREINFTIES1)) NTIES))

(COMMAND "ARRAY" PSECREINFTIESC "SI" "RECTANGULAR" NTIES "1" SPC1 *CANCLE*)
(COMMAND "LINE" PSECREINFL1 PSECREINFL2 *CANCEL*)
(COMMAND "ARRAY" PSECREINFL2 "SI" "RECTANGULAR" "1" NBF SPACINGH *CANCLE*)
(COMMAND "LINE" PSECREINFL2 PSECREINFL3 *CANCEL*)
(COMMAND "LINE" PSECREINFL5 PSECREINFL6 *CANCEL*)
(COMMAND "LINE" PSECREINFX1 PSECREINFX2 *CANCEL*)
(COMMAND "HATCH" "AR-CONC,N" "30" "0" PTSECTION12 CNTR+C)
(COMMAND "ZOOM" "EXTENTS")
)





(DEFUN C:BEAMRECT()
(SETQ B(GETINT "GIVE VALUE OF WEB WIDTH IN MM;"))
(SETQ D(GETINT "GIVE VALUE OF TOTAL DEPTH IN MM;"))
(SETQ DIAB(GETINT "GIVE DIA OF BOTTOM BARS IN MM;"))
(SETQ NBB(GETINT "GIVE NUMBER OF BOTTOM BARS ;"))
(SETQ DIAT(GETINT "GIVE DIA OF TOP BARS IN MM;"))
(SETQ NBT(GETINT "GIVE NUMBER OF TOP BARS ;"))
(SETQ DIAS(GETINT "GIVE DIA OF SHEAR STIRRUPS BARS IN MM;"))
(SETQ SPC(GETINT "GIVE SPACING OF SHEAR STIRRUPS IN MM;"))
(SETQ SCALE(GETINT "GIVE DRAWING SCALE 1: ?  ;"))
(SETQ BEAMNUM(GETSTRING "GIVE BEAM NUMBER ;"))
(SETQ DIMTEXT (* 3 SCALE))
(SETQ PT1(GETPOINT "PICK FIRST CORNER OF THE BEAM ;"))
(SETQ PT2(LIST(+ (NTH 0 PT1) B)(NTH 1 PT1)))
(SETQ PT3(LIST(NTH 0 PT2)(+ (NTH 1 PT2) D)))
(SETQ PT4(LIST(NTH 0 PT1)(NTH 1 PT3)))
(SETQ DDASB (+ 25 (/ DIAB 2)))
(SETQ DDAST (+ 25 (/ DIAT 2)))
(SETQ PT5(LIST(+ (NTH 0 PT1) DDASB)(+ (NTH 1 PT1) DDASB)))
(SETQ PT6(LIST(+ (NTH 0 PT1) DDAST)(- (NTH 1 PT4) DDAST)))
(SETQ PTC1(LIST(+ (NTH 0 PT5) (* 0.25 DIAB))(NTH 1 PT5)))
(SETQ PTC2(LIST(+ (NTH 0 PT6) (* 0.25 DIAT))(NTH 1 PT6)))
(SETQ PT6(LIST(+ (NTH 0 PT1) DDAST)(- (NTH 1 PT4) DDAST)))
(SETQ SPACINGB (/ (- B (* 2 DDASB)) (- NBB 1)))
(SETQ SPACINGT (/ (- B (* 2 DDAST)) (- NBT 1)))
(COMMAND "DONUT" 0 DIAB PT5 NIL)
(COMMAND "DONUT" 0 DIAT PT6 NIL)
(SETQ PTD1(LIST(NTH 0 PT1)(- (NTH 1 PT1) (* 1.2 DIMTEXT))))
(SETQ PTD2(LIST(- (NTH 0 PT1) (* 1.2 DIMTEXT))(NTH 1 PT1)))
(SETQ PTD3(LIST(NTH 0 PT5)(NTH 1 PT5)))
(SETQ PTD4(LIST(NTH 0 PTD3)(+ (NTH 1 PTD3) (* 0.2 D))))
(SETQ PTD5(LIST(+ (NTH 0 PTD4) B)(NTH 1 PTD4)))
(SETQ PTD6(LIST(NTH 0 PT6)(NTH 1 PT6)))
(SETQ PTD7(LIST(NTH 0 PTD6)(- (NTH 1 PTD6) (* 0.2 D))))
(COMMAND "ARRAY" "SI" PTC1 "R" "1" NBB SPACINGB)
(COMMAND "LINE" PTD3 PTD4 *CANCEL*)
(SETQ PTD8(LIST(+ (NTH 0 PTD7) B)(NTH 1 PTD7)))
(COMMAND "ARRAY" "SI" PTC2 "R" "1" NBT SPACINGT)
(COMMAND "LINE" PTD6 PTD7 *CANCEL*)
(COMMAND "ARRAY" "SI" PTD7 "R" "1" NBT SPACINGT)
(COMMAND "DDIM" "RAJ25SCALE")
(COMMAND "ARRAY" "SI" PTD3 "R" "1" NBB SPACINGB)
(COMMAND "DDIM" "RAJ25SCALE")
(COMMAND "PLINE" PT1 PT2 PT3 PT4 "C")
(COMMAND "OFFSET" "25" PT1 PT5 *CANCEL*)
(COMMAND "DIM" "HORIZONTAL" PT1 PT2 "T" B PTD1 *CANCLE*)
(COMMAND "DIM" "VERTICAL" PT1 PT4 "T" D PTD2 *CANCEL*)
(SETQ PTD9(LIST(- (NTH 0 PT2) 25)(+ (NTH 1 PT2) (* 0.50 D))))
(SETQ PTD10(LIST(+ (NTH 0 PTD9) (+ 25 DDASB))(NTH 1 PTD9)))
(COMMAND "LINE" PTD4 PTD5 *CANCEL*)
(COMMAND "LINE" PTD7 PTD8 *CANCEL*)
(COMMAND "LINE" PTD9 PTD10 *CANCEL*)
(SETQ NOTE (STRCAT (ITOA NBB) "NOS." (ITOA DIAB) "MM DIA.TOR BARS"))
(COMMAND "TEXT" PTD5 (* 0.1 D) "0" NOTE)
(SETQ NOTE (STRCAT (ITOA NBT) "NOS." (ITOA DIAT) "MM DIA.TOR BARS"))
(COMMAND "TEXT" PTD8 (* 0.1 D) "0" NOTE)
(SETQ NOTE (STRCAT (ITOA DIAS) "MM DIA.TWO LEGGED STIRRUPS @" (ITOA SPC) "MM C/C."))
(COMMAND "TEXT" PTD10 (* 0.1 D) "0" NOTE)
(SETQ PTD11(LIST(NTH 0 PT1)(- (NTH 1 PT1) (* 4 DIMTEXT))))
(SETQ NOTE (STRCAT "%%UBEAM NO.B-%%U" BEAMNUM))
(COMMAND "TEXT" PTD11 (* 0.125 D) "0" NOTE)
(COMMAND "ZOOM" "C" PTD10 (* 3 D)) 
)



(DEFUN C:BEAMTEE()
(SETQ B(GETINT "GIVE VALUE OF WEB WIDTH IN MM;"))
(SETQ D(GETINT "GIVE VALUE OF TOTAL DEPTH IN MM;"))
(SETQ DF(GETINT "GIVE VALUE OF FLANGE THICKNESS IN MM;"))
(SETQ DIAB(GETINT "GIVE DIA OF BOTTOM BARS IN MM;"))
(SETQ NBB(GETINT "GIVE NUMBER OF BOTTOM BARS ;"))
(SETQ DIAT(GETINT "GIVE DIA OF TOP BARS IN MM;"))
(SETQ NBT(GETINT "GIVE NUMBER OF TOP BARS ;"))
(SETQ DIAS(GETINT "GIVE DIA OF SHEAR STIRRUPS BARS IN MM;"))
(SETQ SPC(GETINT "GIVE SPACING OF SHEAR STIRRUPS IN MM;"))
(SETQ SCALE(GETINT "GIVE DRAWING SCALE 1: ?  ;"))
(SETQ BEAMNUM(GETSTRING "GIVE BEAM NUMBER ;"))
(SETQ DIMTEXT (* 3 SCALE))
(SETQ PT1(GETPOINT "PICK FIRST CORNER OF THE BEAM ;"))
(SETQ PT2(LIST(+ (NTH 0 PT1) B)(NTH 1 PT1)))
(SETQ PT3(LIST(NTH 0 PT2)(+ (NTH 1 PT2) D)))
(SETQ PT4(LIST(NTH 0 PT1)(NTH 1 PT3)))
(SETQ PT201(LIST(+ (NTH 0 PT1) 25)(+ (NTH 1 PT1) 25)))
(SETQ PT202(LIST(- (NTH 0 PT2) 25)(NTH 1 PT201)))
(SETQ PT203(LIST(NTH 0 PT202)(- (NTH 1 PT3) 25)))
(SETQ PT204(LIST(NTH 0 PT201)(NTH 1 PT203)))
(SETQ DDASB (+ 25 (/ DIAB 2)))
(SETQ DDAST (+ 25 (/ DIAT 2)))
(SETQ PT5(LIST(+ (NTH 0 PT1) DDASB)(+ (NTH 1 PT1) DDASB)))
(SETQ PT6(LIST(+ (NTH 0 PT1) DDAST)(- (NTH 1 PT4) DDAST)))
(SETQ PTC1(LIST(+ (NTH 0 PT5) (* 0.25 DIAB))(NTH 1 PT5)))
(SETQ PTC2(LIST(+ (NTH 0 PT6) (* 0.25 DIAT))(NTH 1 PT6)))
(SETQ PT6(LIST(+ (NTH 0 PT1) DDAST)(- (NTH 1 PT4) DDAST)))
(SETQ SPACINGB (/ (- B (* 2 DDASB)) (- NBB 1)))
(SETQ SPACINGT (/ (- B (* 2 DDAST)) (- NBT 1)))
(COMMAND "DONUT" 0 DIAB PT5 NIL)
(COMMAND "DONUT" 0 DIAT PT6 NIL)
(SETQ PTD1(LIST(NTH 0 PT1)(- (NTH 1 PT1) (* 1.2 DIMTEXT))))
(SETQ PTD2(LIST(- (NTH 0 PT1) (* 1.5 DIMTEXT))(NTH 1 PT1)))
(SETQ PTD3(LIST(NTH 0 PT5)(NTH 1 PT5)))
(SETQ PTD4(LIST(NTH 0 PTD3)(+ (NTH 1 PTD3) (* 0.1 D))))
(SETQ PTD5(LIST(+ (NTH 0 PTD4) B)(NTH 1 PTD4)))
(SETQ PTD6(LIST(NTH 0 PT6)(NTH 1 PT6)))
(SETQ PTD7(LIST(NTH 0 PTD6)(+ (NTH 1 PTD5) (* 0.35 D))))
(COMMAND "ARRAY" "SI" PTC1 "R" "1" NBB SPACINGB)
(COMMAND "LINE" PTD3 PTD4 *CANCEL*)
(COMMAND "ARRAY" "SI" PTD4 "R" "1" NBB SPACINGB)
(SETQ PTD8(LIST(+ (NTH 0 PTD7) B)(NTH 1 PTD7)))
(COMMAND "ARRAY" "SI" PTC2 "R" "1" NBT SPACINGT)
(COMMAND "LINE" PTD6 PTD7 *CANCEL*)
(COMMAND "ARRAY" "SI" PTD7 "R" "1" NBT SPACINGT)
(COMMAND "PLINE" PT201 PT202 PT203 PT204 "C")
(SETQ PT101(LIST(NTH 0 PT4)(NTH 1 PT4)))
(SETQ PT102(LIST(NTH 0 PT101)(- (NTH 1 PT101) DF)))
(SETQ PT1012(LIST(NTH 0 PT101)(- (NTH 1 PT101) (/ DF 2))))
(SETQ PT103(LIST(- (NTH 0 PT101) (* 3 B))(NTH 1 PT101)))
(SETQ PT104(LIST(NTH 0 PT103)(- (NTH 1 PT103) DF)))
(SETQ EXT1(/ DF 4))
(SETQ EXT2(/ DF 2))
(SETQ PTEL101(LIST(NTH 0 PT103)(+ (NTH 1 PT103) EXT1)))
(SETQ PTEL102(LIST(NTH 0 PT103)(NTH 1 PT103)))
(SETQ PTEL103(LIST(NTH 0 PTEL101)(- (NTH 1 PTEL102) EXT1)))
(SETQ PTEL104(LIST(+ (NTH 0 PTEL103) EXT1)(NTH 1 PTEL103)))
(SETQ PTEL105(LIST(- (NTH 0 PTEL103) EXT1)(- (NTH 1 PTEL103) EXT2)))
(SETQ PTEL106(LIST(NTH 0 PTEL103)(- (NTH 1 PTEL103) EXT2)))
(SETQ PTEL107(LIST(NTH 0 PT104)(NTH 1 PT104)))
(SETQ PTEL108(LIST(NTH 0 PTEL107)(- (NTH 1 PTEL107) EXT1)))
(COMMAND "LINE" PTEL101 PTEL102 PTEL103 PTEL104 PTEL105 PTEL106 PTEL107 PTEL108 *CANCEL*)
(SETQ PT105(LIST(NTH 0 PT3)(NTH 1 PT3)))
(SETQ PT106(LIST(NTH 0 PT105)(- (NTH 1 PT105) DF)))
(SETQ PT107(LIST(+ (NTH 0 PT105) (* 3 B))(NTH 1 PT105)))
(SETQ PT108(LIST(NTH 0 PT107)(- (NTH 1 PT107) DF)))
(SETQ PTER101(LIST(NTH 0 PT107)(+ (NTH 1 PT107) EXT1)))
(SETQ PTER102(LIST(NTH 0 PT107)(NTH 1 PT107)))
(SETQ PTER103(LIST(NTH 0 PTER101)(- (NTH 1 PTER102) EXT1)))
(SETQ PTER104(LIST(+ (NTH 0 PTER103) EXT1)(NTH 1 PTER103)))
(SETQ PTER105(LIST(- (NTH 0 PTER103) EXT1)(- (NTH 1 PTER103) EXT2)))
(SETQ PTER106(LIST(NTH 0 PTER103)(- (NTH 1 PTER103) EXT2)))
(SETQ PTER107(LIST(NTH 0 PT108)(NTH 1 PT108)))
(SETQ PTER108(LIST(NTH 0 PTER107)(- (NTH 1 PTER107) EXT1)))
(COMMAND "LINE" PTER101 PTER102 PTER103 PTER104 PTER105 PTER106 PTER107 PTER108 *CANCEL*)
(COMMAND "LINE" PT104 PT102 PT1 PT2 PT106 PT108 *CANCLE*)
(COMMAND "LINE" PT103 PT107 *CANCEL*)
(COMMAND "DIM" "HORIZONTAL" PT1 PT2 "T" B PTD1 *CANCLE*)
(COMMAND "DIM" "VERTICAL" PT1 PT4 "T" D PTD2 *CANCEL*)
(SETQ PTD101(LIST(- (NTH 0 PTEL103) DF)(NTH 1 PT103)))
(COMMAND "DIM" "VERTICAL" PTEL102 PTEL107 "T" DF PTD101 *CANCEL*)
(SETQ PTD9(LIST(- (NTH 0 PT2) 25)(+ (NTH 1 PTD5) (* 0.2 D))))
(SETQ PTD10(LIST(NTH 0 PTD5)(NTH 1 PTD9)))
(COMMAND "LINE" PTD4 PTD5 *CANCEL*)
(COMMAND "LINE" PTD7 PTD8 *CANCEL*)
(COMMAND "LINE" PTD9 PTD10 *CANCEL*)
(SETQ NOTE (STRCAT (ITOA NBB) "NOS." (ITOA DIAB) "MM DIA.TOR BARS"))
(COMMAND "TEXT" PTD5 (* 0.1 D) "0" NOTE)
(SETQ NOTE (STRCAT (ITOA NBT) "NOS." (ITOA DIAT) "MM DIA.TOR BARS"))
(COMMAND "TEXT" PTD8 (* 0.1 D) "0" NOTE)
(SETQ NOTE (STRCAT (ITOA DIAS) "MM DIA.TWO LEGGED STIRRUPS @" (ITOA SPC) "MM C/C."))
(COMMAND "TEXT" PTD10 (* 0.1 D) "0" NOTE)
(SETQ PTD11(LIST(NTH 0 PT1)(- (NTH 1 PT1) (* 4 DIMTEXT))))
(SETQ NOTE (STRCAT "%%UBEAM NO.B-%%U" BEAMNUM))
(COMMAND "TEXT" PTD11 (* 0.125 D) "0" NOTE)
(COMMAND "ZOOM" "C" PTD10 (* 3.5 D)) 
)



(DEFUN C:BEAML()
(SETQ B(GETINT "GIVE VALUE OF WEB WIDTH IN MM;"))
(SETQ D(GETINT "GIVE VALUE OF TOTAL DEPTH IN MM;"))
(SETQ DFT(GETINT "GIVE VALUE OF TOP FLANGE THICKNESS IN MM;"))
(SETQ DFB(GETINT "GIVE VALUE OF BOTTOM FLANGE THICKNESS IN MM;"))
(SETQ DIAB(GETINT "GIVE DIA OF BOTTOM BARS IN MM;"))
(SETQ NBB(GETINT "GIVE NUMBER OF BOTTOM BARS ;"))
(SETQ DIAT(GETINT "GIVE DIA OF TOP BARS IN MM;"))
(SETQ NBT(GETINT "GIVE NUMBER OF TOP BARS ;"))
(SETQ DIAS(GETINT "GIVE DIA OF SHEAR STIRRUPS BARS IN MM;"))
(SETQ SPC(GETINT "GIVE SPACING OF SHEAR STIRRUPS IN MM;"))
(SETQ SCALE(GETINT "GIVE DRAWING SCALE 1: ?  ;"))
(SETQ BEAMNUM(GETSTRING "GIVE BEAM NUMBER ;"))
(SETQ DIMTEXT (* 3 SCALE))
(SETQ PT1(GETPOINT "PICK FIRST CORNER OF THE BEAM ;"))
(SETQ PT2(LIST(+ (NTH 0 PT1) B)(NTH 1 PT1)))
(SETQ PT3(LIST(NTH 0 PT2)(+ (NTH 1 PT2) D)))
(SETQ PT4(LIST(NTH 0 PT1)(NTH 1 PT3)))
(SETQ PT201(LIST(+ (NTH 0 PT1) 25)(+ (NTH 1 PT1) 25)))
(SETQ PT202(LIST(- (NTH 0 PT2) 25)(NTH 1 PT201)))
(SETQ PT203(LIST(NTH 0 PT202)(- (NTH 1 PT3) 25)))
(SETQ PT204(LIST(NTH 0 PT201)(NTH 1 PT203)))
(SETQ DDASB (+ 25 (/ DIAB 2)))
(SETQ DDAST (+ 25 (/ DIAT 2)))
(SETQ PT5(LIST(+ (NTH 0 PT1) DDASB)(+ (NTH 1 PT1) DDASB)))
(SETQ PT6(LIST(+ (NTH 0 PT1) DDAST)(- (NTH 1 PT4) DDAST)))
(SETQ PTC1(LIST(+ (NTH 0 PT5) (* 0.25 DIAB))(NTH 1 PT5)))
(SETQ PTC2(LIST(+ (NTH 0 PT6) (* 0.25 DIAT))(NTH 1 PT6)))
(SETQ PT6(LIST(+ (NTH 0 PT1) DDAST)(- (NTH 1 PT4) DDAST)))
(SETQ SPACINGB (/ (- B (* 2 DDASB)) (- NBB 1)))
(SETQ SPACINGT (/ (- B (* 2 DDAST)) (- NBT 1)))
(COMMAND "DONUT" 0 DIAB PT5 NIL)
(COMMAND "DONUT" 0 DIAT PT6 NIL)
(SETQ PTD1(LIST(NTH 0 PT1)(- (NTH 1 PT1) (* 1.2 DIMTEXT))))
(SETQ PTD2(LIST(- (NTH 0 PT1) (* 1.5 DIMTEXT))(NTH 1 PT1)))
(SETQ PTD3(LIST(NTH 0 PT5)(NTH 1 PT5)))
(SETQ PTD4(LIST(NTH 0 PTD3)(+ (NTH 1 PTD3) (* 0.25 D))))
(SETQ PTD5(LIST(+ (NTH 0 PTD4) B)(NTH 1 PTD4)))
(SETQ PTD6(LIST(NTH 0 PT6)(NTH 1 PT6)))
(SETQ PTD7(LIST(NTH 0 PTD6)(+ (NTH 1 PTD5) (* 0.35 D))))
(COMMAND "ARRAY" "SI" PTC1 "R" "1" NBB SPACINGB)
(COMMAND "LINE" PTD3 PTD4 *CANCEL*)
(COMMAND "ARRAY" "SI" PTD4 "R" "1" NBB SPACINGB)
(SETQ PTD8(LIST(+ (NTH 0 PTD7) B)(NTH 1 PTD7)))
(COMMAND "ARRAY" "SI" PTC2 "R" "1" NBT SPACINGT)
(COMMAND "LINE" PTD6 PTD7 *CANCEL*)
(COMMAND "ARRAY" "SI" PTD7 "R" "1" NBT SPACINGT)
(COMMAND "PLINE" PT201 PT202 PT203 PT204 "C")
(SETQ PT101(LIST(NTH 0 PT4)(NTH 1 PT4)))
(SETQ PT102(LIST(NTH 0 PT101)(- (NTH 1 PT101) DFT)))
(SETQ PT1012(LIST(NTH 0 PT101)(- (NTH 1 PT101) (/ DFT 2))))
(SETQ PT103(LIST(- (NTH 0 PT101) (* 3 B))(NTH 1 PT101)))
(SETQ PT104(LIST(NTH 0 PT103)(- (NTH 1 PT103) DFT)))
(SETQ EXT1(/ DFT 4))
(SETQ EXT2(/ DFT 2))
(SETQ PTEL101(LIST(NTH 0 PT103)(+ (NTH 1 PT103) EXT1)))
(SETQ PTEL102(LIST(NTH 0 PT103)(NTH 1 PT103)))
(SETQ PTEL103(LIST(NTH 0 PTEL101)(- (NTH 1 PTEL102) EXT1)))
(SETQ PTEL104(LIST(+ (NTH 0 PTEL103) EXT1)(NTH 1 PTEL103)))
(SETQ PTEL105(LIST(- (NTH 0 PTEL103) EXT1)(- (NTH 1 PTEL103) EXT2)))
(SETQ PTEL106(LIST(NTH 0 PTEL103)(- (NTH 1 PTEL103) EXT2)))
(SETQ PTEL107(LIST(NTH 0 PT104)(NTH 1 PT104)))
(SETQ PTEL108(LIST(NTH 0 PTEL107)(- (NTH 1 PTEL107) EXT1)))
(COMMAND "LINE" PTEL101 PTEL102 PTEL103 PTEL104 PTEL105 PTEL106 PTEL107 PTEL108 *CANCEL*)
(SETQ PT105(LIST(NTH 0 PT3)(+ (NTH 1 PT2) DFB)))
(SETQ PT106(LIST(NTH 0 PT2)(NTH 1 PT2)))
(SETQ PT107(LIST(+ (NTH 0 PT105) (* 3 B))(NTH 1 PT105)))
(SETQ PT108(LIST(NTH 0 PT107)(NTH 1 PT2)))
(SETQ EXT1(/ DFB 4))
(SETQ EXT2(/ DFB 2))
(SETQ PTER101(LIST(NTH 0 PT107)(+ (NTH 1 PT107) EXT1)))
(SETQ PTER102(LIST(NTH 0 PT107)(NTH 1 PT107)))
(SETQ PTER103(LIST(NTH 0 PTER101)(- (NTH 1 PTER102) EXT1)))
(SETQ PTER104(LIST(+ (NTH 0 PTER103) EXT1)(NTH 1 PTER103)))
(SETQ PTER105(LIST(- (NTH 0 PTER103) EXT1)(- (NTH 1 PTER103) EXT2)))
(SETQ PTER106(LIST(NTH 0 PTER103)(- (NTH 1 PTER103) EXT2)))
(SETQ PTER107(LIST(NTH 0 PT108)(NTH 1 PT108)))
(SETQ PTER108(LIST(NTH 0 PTER107)(- (NTH 1 PTER107) EXT1)))
(COMMAND "LINE" PTER101 PTER102 PTER103 PTER104 PTER105 PTER106 PTER107 PTER108 *CANCEL*)
(COMMAND "LINE" PT104 PT102 PT1 PT108 *CANCLE*)
(COMMAND "LINE" PT103 PT3 PT105 PT107 *CANCEL*)
(COMMAND "DIM" "HORIZONTAL" PT1 PT2 "T" B PTD1 *CANCLE*)
(COMMAND "DIM" "VERTICAL" PT1 PT4 "T" D PTD2 *CANCEL*)
(SETQ PTD101(LIST(- (NTH 0 PTEL103) DFT)(NTH 1 PT103)))
(SETQ PTD102(LIST(+ (NTH 0 PTER103) DFB)(NTH 1 PTER103)))
(COMMAND "DIM" "VERTICAL" PTEL102 PTEL107 "T" DFT PTD101 *CANCEL*)
(COMMAND "DIM" "VERTICAL" PTER102 PTER107 "T" DFB PTD102 *CANCEL*)
(SETQ PTD9(LIST(- (NTH 0 PT2) 25)(+ (NTH 1 PTD5) (* 0.2 D))))
(SETQ PTD10(LIST(NTH 0 PTD5)(NTH 1 PTD9)))
(COMMAND "LINE" PTD4 PTD5 *CANCEL*)
(COMMAND "LINE" PTD7 PTD8 *CANCEL*)
(COMMAND "LINE" PTD9 PTD10 *CANCEL*)
(SETQ NOTE (STRCAT (ITOA NBB) "NOS." (ITOA DIAB) "MM DIA.TOR BARS"))
(COMMAND "TEXT" PTD5 (* 0.1 D) "0" NOTE)
(SETQ NOTE (STRCAT (ITOA NBT) "NOS." (ITOA DIAT) "MM DIA.TOR BARS"))
(COMMAND "TEXT" PTD8 (* 0.1 D) "0" NOTE)
(SETQ NOTE (STRCAT (ITOA DIAS) "MM DIA.TWO LEGGED STIRRUPS @" (ITOA SPC) "MM C/C."))
(COMMAND "TEXT" PTD10 (* 0.1 D) "0" NOTE)
(SETQ PTD11(LIST(NTH 0 PT1)(- (NTH 1 PT1) (* 4 DIMTEXT))))
(SETQ NOTE (STRCAT "%%UBEAM NO.B-%%U" BEAMNUM))
(COMMAND "TEXT" PTD11 (* 0.125 D) "0" NOTE)
(COMMAND "ZOOM" "C" PTD10 (* 3.5 D))
(SETQ PT1(LIST(NTH 0 PT1)(+ (NTH 1 PT4) (* 4 DIMTEXT))))
)



(DEFUN C:COLUCRCL()
(SETQ D(GETINT "GIVE VALUE OF DIAMETER OF THE COLUMN IN MM;"))
(SETQ DIAL(GETINT "GIVE DIA OF LONGITUDINAL REINFORCEMENT BARS IN MM;"))
(SETQ NBTOTAL(GETINT "GIVE TOTAL NUMBER OF BARS IN THE COLUMN;"))
(SETQ DIAT(GETINT "GIVE DIA OF LATERAL TIES IN MM;"))
(SETQ SPC(GETINT "GIVE SPACING OF LATERAL TIES IN MM;"))
(SETQ SCALE(GETINT "GIVE DRAWING SCALE 1: ?  ;"))
(SETQ COLUMNUM(GETSTRING "GIVE COLUMN NUMBER C- ;"))
(SETQ DIMTEXT (* 3 SCALE))
(SETQ PT1(GETPOINT "PICK FIRST EDGE OF THE COLUMN ;"))
(SETQ PT1DAS(LIST(+ (NTH 0 PT1) D)(NTH 1 PT1)))
(SETQ PT2(LIST(+ (NTH 0 PT1) (/ D 2))(NTH 1 PT1)))
(SETQ DDASL (+ 25 (/ DIAL 2)))
(SETQ PT3(LIST(+ (NTH 0 PT1) DDASL)(NTH 1 PT1)))
(SETQ PTC1(LIST(+ (NTH 0 PT3) (* 0.25 DIAL))(NTH 1 PT3)))
(COMMAND "DONUT" 0 DIAL PT3 *CANCLE*)
(SETQ PT4(LIST(+ (NTH 0 PT1) (/ D 2)) (- (NTH 1 PT1) (/ D 2))))
(COMMAND "ARRAY" PTC1 "SI" "POLAR" PT2 NBTOTAL 360 "Y" *CANCLE*)
(SETQ PT5(LIST(NTH 0 PT4)(+ (NTH 1 PT4) D)))
(SETQ PTD1(LIST(+ (NTH 0 PT1) (+ D (* 1.75 DIMTEXT)))(NTH 1 PT4)))
(SETQ PTD2(LIST(NTH 0 PT1)(+ (NTH 1 PT5) (* 0.2 D))))
(SETQ PTD3(LIST(NTH 0 PTD2)(- (NTH 1 PT4) (* 0.2 D))))
(SETQ X(- (/ D 2) 25))
(SETQ PTD4(LIST(- (NTH 0 PT2) (* X (COS 0.785)))(- (NTH 1 PT2) (* X (SIN 0.785)))))
(SETQ PTD5(LIST(+ (NTH 0 PTD2) 50)(NTH 1 PTD2)))
(SETQ PTD6(LIST(+ (NTH 0 PTD3) 50)(NTH 1 PTD3)))
(COMMAND "CIRCLE"  "2P" PT1 PT1DAS *CANCLE*)
(COMMAND "OFFSET" "25" PT1 PT2 *CANCEL*)
(COMMAND "DIM" "VERTICAL" PT4 PT5 "T" D PTD1 *CANCEL*)
(SETQ NOTE (STRCAT (ITOA NBTOTAL) "NOS." (ITOA DIAL) "MM DIA.TOR BARS"))
(COMMAND "TEXT" PTD5 (* 0.1 D) "0" NOTE *CANCLE*)
(SETQ NOTE (STRCAT "" (ITOA DIAT) "MM DIA.LATERAL RINGS @" (ITOA SPC) "MM C/C."))
(COMMAND "TEXT" PTD6 (* 0.1 D) "0" NOTE *CANCLE*)
(SETQ PTD11(LIST(NTH 0 PTD3)(- (NTH 1 PTD3) (* 2 DIMTEXT))))
(SETQ NOTE (STRCAT "%%UCOLUMN C-%%U" COLUMNUM))
(COMMAND "TEXT" PTD11 (* 0.125 D) "0" NOTE *CANCLE*)
(COMMAND "DIM" "LEADER" PT3 PTD2 PTD5 *CANCLE*)
(COMMAND "DIM" "LEADER" PTD4 PTD3 PTD6 *CANCLE*)
(COMMAND "ZOOM" "C" PT2 (* 3.5 D)) 
)



(DEFUN C:BEAMINTEE()
(SETQ B(GETINT "GIVE VALUE OF WEB WIDTH IN MM;"))
(SETQ D(GETINT "GIVE VALUE OF TOTAL DEPTH IN MM;"))
(SETQ DFB(GETINT "GIVE VALUE OF BOTTOM FLANGE THICKNESS IN MM;"))
(SETQ DIAB(GETINT "GIVE DIA OF BOTTOM BARS IN MM;"))
(SETQ NBB(GETINT "GIVE NUMBER OF BOTTOM BARS ;"))
(SETQ DIAT(GETINT "GIVE DIA OF TOP BARS IN MM;"))
(SETQ NBT(GETINT "GIVE NUMBER OF TOP BARS ;"))
(SETQ DIAS(GETINT "GIVE DIA OF SHEAR STIRRUPS BARS IN MM;"))
(SETQ SPC(GETINT "GIVE SPACING OF SHEAR STIRRUPS IN MM;"))
(SETQ SCALE(GETINT "GIVE DRAWING SCALE 1: ?  ;"))
(SETQ BEAMNUM(GETSTRING "GIVE BEAM NUMBER ;"))
(SETQ DIMTEXT (* 3 SCALE))
(SETQ PT1(GETPOINT "PICK FIRST CORNER OF THE BEAM ;"))
(SETQ PT2(LIST(+ (NTH 0 PT1) B)(NTH 1 PT1)))
(SETQ PT3(LIST(NTH 0 PT2)(+ (NTH 1 PT2) D)))
(SETQ PT4(LIST(NTH 0 PT1)(NTH 1 PT3)))
(SETQ PT201(LIST(+ (NTH 0 PT1) 25)(+ (NTH 1 PT1) 25)))
(SETQ PT202(LIST(- (NTH 0 PT2) 25)(NTH 1 PT201)))
(SETQ PT203(LIST(NTH 0 PT202)(- (NTH 1 PT3) 25)))
(SETQ PT204(LIST(NTH 0 PT201)(NTH 1 PT203)))
(SETQ DDASB (+ 25 (/ DIAB 2)))
(SETQ DDAST (+ 25 (/ DIAT 2)))
(SETQ PT5(LIST(+ (NTH 0 PT1) DDASB)(+ (NTH 1 PT1) DDASB)))
(SETQ PT6(LIST(+ (NTH 0 PT1) DDAST)(- (NTH 1 PT4) DDAST)))
(SETQ PTC1(LIST(+ (NTH 0 PT5) (* 0.25 DIAB))(NTH 1 PT5)))
(SETQ PTC2(LIST(+ (NTH 0 PT6) (* 0.25 DIAT))(NTH 1 PT6)))
(SETQ PT6(LIST(+ (NTH 0 PT1) DDAST)(- (NTH 1 PT4) DDAST)))
(SETQ SPACINGB (/ (- B (* 2 DDASB)) (- NBB 1)))
(SETQ SPACINGT (/ (- B (* 2 DDAST)) (- NBT 1)))
(COMMAND "DONUT" 0 DIAB PT5 NIL)
(COMMAND "DONUT" 0 DIAT PT6 NIL)
(SETQ PTD1(LIST(NTH 0 PT1)(- (NTH 1 PT1) (* 1.2 DIMTEXT))))
(SETQ PTD2(LIST(- (NTH 0 PT1) (* 1.5 DIMTEXT))(NTH 1 PT1)))
(SETQ PTD3(LIST(NTH 0 PT5)(NTH 1 PT5)))
(SETQ PTD4(LIST(NTH 0 PTD3)(+ (NTH 1 PTD3) (* 0.25 D))))
(SETQ PTD5(LIST(+ (NTH 0 PTD4) B)(NTH 1 PTD4)))
(SETQ PTD6(LIST(NTH 0 PT6)(NTH 1 PT6)))
(SETQ PTD7(LIST(NTH 0 PTD6)(+ (NTH 1 PTD5) (* 0.35 D))))
(COMMAND "ARRAY" "SI" PTC1 "R" "1" NBB SPACINGB)
(COMMAND "LINE" PTD3 PTD4 *CANCEL*)
(COMMAND "ARRAY" "SI" PTD4 "R" "1" NBB SPACINGB)
(SETQ PTD8(LIST(+ (NTH 0 PTD7) B)(NTH 1 PTD7)))
(COMMAND "ARRAY" "SI" PTC2 "R" "1" NBT SPACINGT)
(COMMAND "LINE" PTD6 PTD7 *CANCEL*)
(COMMAND "ARRAY" "SI" PTD7 "R" "1" NBT SPACINGT)
(COMMAND "PLINE" PT201 PT202 PT203 PT204 "C")
(SETQ PT101(LIST(NTH 0 PT1)(+ (NTH 1 PT1) DFB)))
(SETQ PT102(LIST(NTH 0 PT101)(- (NTH 1 PT101) DFB)))
(SETQ PT1012(LIST(NTH 0 PT101)(- (NTH 1 PT101) (/ DFB 2))))
(SETQ PT103(LIST(- (NTH 0 PT101) (* 3 B))(NTH 1 PT101)))
(SETQ PT104(LIST(NTH 0 PT103)(- (NTH 1 PT103) DFB)))
(SETQ EXT1(/ DFB 4))
(SETQ EXT2(/ DFB 2))
(SETQ PTEL101(LIST(NTH 0 PT103)(+ (NTH 1 PT103) EXT1)))
(SETQ PTEL102(LIST(NTH 0 PT103)(NTH 1 PT103)))
(SETQ PTEL103(LIST(NTH 0 PTEL101)(- (NTH 1 PTEL102) EXT1)))
(SETQ PTEL104(LIST(+ (NTH 0 PTEL103) EXT1)(NTH 1 PTEL103)))
(SETQ PTEL105(LIST(- (NTH 0 PTEL103) EXT1)(- (NTH 1 PTEL103) EXT2)))
(SETQ PTEL106(LIST(NTH 0 PTEL103)(- (NTH 1 PTEL103) EXT2)))
(SETQ PTEL107(LIST(NTH 0 PT104)(NTH 1 PT104)))
(SETQ PTEL108(LIST(NTH 0 PTEL107)(- (NTH 1 PTEL107) EXT1)))
(COMMAND "LINE" PTEL101 PTEL102 PTEL103 PTEL104 PTEL105 PTEL106 PTEL107 PTEL108 *CANCEL*)
(SETQ PT105(LIST(NTH 0 PT3)(+ (NTH 1 PT2) DFB)))
(SETQ PT106(LIST(NTH 0 PT2)(NTH 1 PT2)))
(SETQ PT107(LIST(+ (NTH 0 PT105) (* 3 B))(NTH 1 PT105)))
(SETQ PT108(LIST(NTH 0 PT107)(NTH 1 PT2)))
(SETQ EXT1(/ DFB 4))
(SETQ EXT2(/ DFB 2))
(SETQ PTER101(LIST(NTH 0 PT107)(+ (NTH 1 PT107) EXT1)))
(SETQ PTER102(LIST(NTH 0 PT107)(NTH 1 PT107)))
(SETQ PTER103(LIST(NTH 0 PTER101)(- (NTH 1 PTER102) EXT1)))
(SETQ PTER104(LIST(+ (NTH 0 PTER103) EXT1)(NTH 1 PTER103)))
(SETQ PTER105(LIST(- (NTH 0 PTER103) EXT1)(- (NTH 1 PTER103) EXT2)))
(SETQ PTER106(LIST(NTH 0 PTER103)(- (NTH 1 PTER103) EXT2)))
(SETQ PTER107(LIST(NTH 0 PT108)(NTH 1 PT108)))
(SETQ PTER108(LIST(NTH 0 PTER107)(- (NTH 1 PTER107) EXT1)))
(COMMAND "LINE" PTER101 PTER102 PTER103 PTER104 PTER105 PTER106 PTER107 PTER108 *CANCEL*)
(COMMAND "LINE" PT104 PT108 *CANCLE*)
(COMMAND "LINE" PT103 PT101 PT4 PT3 PT105 PT107 *CANCEL*)
(COMMAND "DIM" "HORIZONTAL" PT1 PT2 "T" B PTD1 *CANCLE*)
(COMMAND "DIM" "VERTICAL" PT1 PT4 "T" D PTD2 *CANCEL*)
(SETQ PTD101(LIST(- (NTH 0 PTEL103) DFB)(NTH 1 PT103)))
(SETQ PTD102(LIST(+ (NTH 0 PTER103) DFB)(NTH 1 PTER103)))
(COMMAND "DIM" "VERTICAL" PTEL102 PTEL107 "T" DFB PTD101 *CANCEL*)
(SETQ PTD9(LIST(- (NTH 0 PT2) 25)(+ (NTH 1 PTD5) (* 0.2 D))))
(SETQ PTD10(LIST(NTH 0 PTD5)(NTH 1 PTD9)))
(COMMAND "LINE" PTD4 PTD5 *CANCEL*)
(COMMAND "LINE" PTD7 PTD8 *CANCEL*)
(COMMAND "LINE" PTD9 PTD10 *CANCEL*)
(SETQ NOTE (STRCAT (ITOA NBB) "NOS." (ITOA DIAB) "MM DIA.TOR BARS"))
(COMMAND "TEXT" PTD5 (* 0.1 D) "0" NOTE)
(SETQ NOTE (STRCAT (ITOA NBT) "NOS." (ITOA DIAT) "MM DIA.TOR BARS"))
(COMMAND "TEXT" PTD8 (* 0.1 D) "0" NOTE)
(SETQ NOTE (STRCAT (ITOA DIAS) "MM DIA.TWO LEGGED STIRRUPS @" (ITOA SPC) "MM C/C."))
(COMMAND "TEXT" PTD10 (* 0.1 D) "0" NOTE)
(SETQ PTD11(LIST(NTH 0 PT1)(- (NTH 1 PT1) (* 4 DIMTEXT))))
(SETQ NOTE (STRCAT "%%UBEAM NO.B-%%U" BEAMNUM))
(COMMAND "TEXT" PTD11 (* 0.125 D) "0" NOTE)
(COMMAND "ZOOM" "C" PTD10 (* 3.5 D))
(SETQ PT1(LIST(NTH 0 PT1)(+ (NTH 1 PT4) (* 4 DIMTEXT))))
)

)
